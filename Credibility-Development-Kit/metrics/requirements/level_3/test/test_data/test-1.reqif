# Requirement Specification from Setlabs

# Specification: aa

## 1
System Requirements Specification
- Signee: PM
- Creator: PM
- Customer: CS1
- Owner: CS0
- Status.date: 22.04.22
- Target: Moto1
- Function Types: Nonfunctional
- Status.status: CREATED

## 2
Brake Requirement
PLACEHOLDER
- Signee: Leader2
- Creator: Leader1
- Customer: CS2
- Owner: CS1
- Testcase: 1.2
- Status.date: 22.01.22
- Target: Moto2
- Function Types: Nonfunctional
- Status.status: CREATED

### 2.1
Asymptotic pressure >= 15
- Signee: Leader3
- Creator: Tester1
- Customer: CS3
- Owner: CS1
- Testcase: 1.3
- Status.date: 11.02.21
- Target: Battery
- version: 1
- Function Types: Nonfunctional
- Status.status: CREATED
